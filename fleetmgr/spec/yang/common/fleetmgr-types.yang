module fleetmgr-types {
  yang-version "1.1";
  namespace "urn:fleetmgr:types";
  prefix fleetmgr-types;

  import ietf-inet-types {
    prefix inet;
  }
  import stratoweave-ssh {
    prefix sw-ssh;
  }

  grouping device-options {
    leaf description {
      type string;
    }

    list address {
      key name;
      leaf name {
        description "Name of address, e.g. 'loopback' or 'OOB'";
        type string;
      }
      leaf address {
        type inet:host;
        mandatory true;
      }
      leaf port {
        type uint16;
      }
      list initial-credentials {
        key "username password key";
        leaf username {
          type string;
        }
        leaf password {
          type string;
        }
        leaf key {
          type string;
        }
      }
    }

    container credentials {
      leaf username {
        type string;
        mandatory true;
      }
      leaf password {
        type string;
      }
      list key {
        key key;
        leaf key {
          type string;
        }
        leaf private-key {
          type string;
        }
      }
    }

    list initial-credentials {
      key "username password key";
      leaf username {
        type string;
      }
      leaf password {
        type string;
      }
      leaf key {
        type string;
      }
    }

    list extra-adapter {
      key type;
      ordered-by user;
      description
        "Adapters that run beside the adapter of the device type, for the
         modules that adapter does not have, such as iosxe-cli beside the
         NETCONF adapter of an IOS XE device. Passed to the device as its
         extra-adapter list.";
      leaf type {
        description "Device type of the adapter.";
        type string;
      }
      leaf address {
        description "The address to connect to. Default: the first.";
        type leafref {
          path "../../address/name";
        }
      }
      leaf port {
        description
          "Port to connect to. Default: the adapter's own. The port of the
           address is for the adapter of the device type.";
        type uint16;
      }
      container credentials {
        presence "Use these credentials instead of the device's.";
        leaf username {
          type string;
          mandatory true;
        }
        leaf password {
          type string;
        }
        list key {
          key key;
          leaf key {
            type string;
          }
          leaf private-key {
            type string;
          }
        }
      }
      container ssh {
        presence "Use these SSH settings instead of the device's.";
        uses sw-ssh:ssh-client-config;
      }
    }

    container ssh {
      description
        "SSH transport parameters used when connecting to this device. Applies
         to every SSH-based adapter (NETCONF over SSH, CLI, ...), except an
         extra adapter that has its own.";
      uses sw-ssh:ssh-client-config;
    }

    leaf approval-required {
      description "Require approval of each individual configuration change to this device";
      type boolean;
      default "false";
    }

    leaf sync-check {
      type boolean;
      default true;
      description
        "Check that the device configuration is in sync before applying edits.";
    }

    container mock {
      leaf enabled {
        type boolean;
        default "false";
      }
      container software {
        description
          "How the mock behaves during a software upgrade.";
        leaf upgrade-duration {
          description
            "Seconds a whole mock software upgrade takes, spread over its
             operations as measured on a real device. Absent or 0 completes
             each operation at once.";
          units "seconds";
          type uint16;
        }
        leaf upgrade-duration-variance {
          description
            "How much the duration of each mock software upgrade varies, as
             a percentage of upgrade-duration in either direction. Each
             upgrade draws its duration evenly between upgrade-duration
             x (1 - v/100) and upgrade-duration x (1 + v/100) when it
             starts. 0 makes every upgrade take exactly upgrade-duration.";
          units "percent";
          type uint8 {
            range "0..100";
          }
          default 20;
        }
        leaf failure {
          description
            "IOS XE failure the mock reproduces during an upgrade.";
          type enumeration {
            enum none;
            enum download-failed {
              description "The download fails after xcopy was accepted.";
            }
            enum add-failed {
              description "The verify stage fails after install add was accepted.";
            }
            enum activate-refused {
              description "activate is rejected, as when the image was not added.";
            }
            enum commit-failed {
              description "The commit stage fails after install-commit was accepted.";
            }
            enum reverts {
              description "The abort timer runs out before the commit.";
            }
            enum bgp-down {
              description "The BGP session is idle from the start.";
            }
            enum bgp-lost {
              description
                "The BGP session is idle while the activated release runs,
                 until a commit or an abort.";
            }
          }
          default "none";
        }
      }
      container platform {
        description
          "The platform the mock reports.";
        leaf version {
          description
            "Release the mock runs before any upgrade; an install changes it.
             Absent means 17.18.02.";
          type string;
        }
        leaf model {
          description
            "Chassis product id. Absent means C8000V.";
          type string;
        }
        leaf serial-number {
          description
            "Chassis serial number. Absent means 9ABCDEFGHIJ.";
          type string;
        }
      }
      list module {
        key "name";
        leaf name {
          type string;
        }
        leaf namespace {
          type string;
          mandatory true;
        }
        leaf revision {
          type string;
        }
        leaf-list feature {
          type string;
        }
      }
    }

    container debug {
      leaf connection {
        type boolean;
        default "false";
      }
      leaf log-level {
        description
          "Log level for this device's log file.";
        type enumeration {
          enum off;
          enum error;
          enum warning;
          enum info;
          enum debug;
          enum trace;
        }
      }
    }

    container feature-flags {
      leaf runtime-schema-fetch {
        type boolean;
        default false;
      }
    }
  }

  grouping upgrade-checks {
    container upgrade-checks {
      description
        "How long the flotilla's BGP upgrade checks wait before they refuse.
         An absent leaf keeps the flotilla's default, 45 s before the
         install and 600 s after it.";
      leaf enabled {
        description
          "Whether the BGP checks gate the device's upgrade. A device whose
           BGP state no adapter reads fails the pre-check unless they are
           off.";
        type boolean;
        default "true";
      }
      leaf precheck-wait {
        units "seconds";
        type uint16 {
          range "1..max";
        }
      }
      leaf postcheck-wait {
        units "seconds";
        type uint16 {
          range "1..max";
        }
      }
    }
  }

  grouping software-options {
    container software {
      leaf upgrade-campaign {
        description
          "The campaign that holds this device. A device is in one
           campaign at most: an edit that gives it a second campaign
           fails.";
        type string;
      }
      leaf target-release {
        type string;
      }
      leaf attempt {
        description
          "The attempt of the intent: a new value makes the device read its
           release again and run a failed upgrade again.";
        type uint32;
        default "0";
      }
      leaf image-url {
        type string;
      }
      list image-checksum {
        key algorithm;
        leaf algorithm {
          type enumeration {
            enum md5;
            enum sha256;
            enum sha512;
          }
        }
        leaf digest {
          type string {
            pattern '[0-9a-fA-F]+';
          }
          mandatory true;
        }
      }
      leaf image-size {
        type uint64;
        units "bytes";
      }
      leaf allow-staging {
        description
          "Whether the device may prepare its target release while a veto
           holds the install. Its campaign sets it from the device's turn
           to prepare until the prepare ends, the device is released, or a
           window of its schedule opens.";
        type boolean;
        default "false";
      }
      list veto {
        key holder;
        leaf holder {
          type string;
        }
        leaf reason {
          type string;
        }
      }
    }
  }

  grouping check-result {
    description
      "A software upgrade check verdict as the device reports it, relayed as
       strings like the status: verdict is not-run, pass or fail, and at is
       when it was reached.";
    leaf verdict {
      type string;
    }
    leaf detail {
      type string;
    }
    leaf at {
      type string;
    }
  }

  grouping platform {
    description
      "What a device is, as its flotilla reads it when the device connects.";
    leaf os {
      type string;
    }
    leaf version {
      type string;
    }
    leaf model {
      type string;
    }
    leaf serial-number {
      type string;
    }
  }

  grouping attempt-status {
    description
      "One attempt of a device's software upgrade as the flotilla reports
       it.";
    leaf status {
      type string;
    }
    leaf stage {
      description
        "The step the attempt's run is in, or the step it ended in:
         prepare, precheck, install, postcheck, commit or rollback.";
      type string;
    }
    leaf reason {
      description
        "Why the attempt's run failed or rolled back, as the device's
         software manager reports it.";
      type string;
    }
    container prepare {
      description
        "The device's prepare of its image, from the attempt's
         job[prepare], as its flotilla reports it: state is running, done
         or failed, release is the release it copies or copied, and
         message says why it failed. The attempt's run fills the same
         entry.";
      leaf state {
        type string;
      }
      leaf release {
        type string;
      }
      leaf started {
        type string;
      }
      leaf ended {
        type string;
      }
      leaf message {
        type string;
      }
      leaf progress {
        description
          "How far the prepare is while it runs, as the device's software
           manager reports it: the part of the image that the device has
           transferred.";
        units "percent";
        type uint8 {
          range "0..100";
        }
      }
    }
    container install {
      description
        "The device's install of its target, from the attempt's
         job[install], as its flotilla reports it: state is running, done
         or failed, and release is the release it installs or installed.
         While it runs, message
         says what the device does, e.g. 'add: extract' or 'waiting for the
         device to boot'; when it failed, why; after it, until the commit
         or the rollback, when the commit window ends.";
      leaf state {
        type string;
      }
      leaf release {
        type string;
      }
      leaf started {
        type string;
      }
      leaf ended {
        type string;
      }
      leaf message {
        type string;
      }
    }
    container precheck {
      uses check-result;
    }
    container postcheck {
      uses check-result;
    }
  }

  grouping vetoes {
    list veto {
      description
        "The vetoes that hold the device's install, by holder, as its
         software manager reports them.";
      key holder;
      leaf holder {
        type string;
      }
      leaf reason {
        type string;
      }
    }
  }

  grouping upgrade-status {
    description
      "A device's software upgrade state as the flotilla reports it.";
    leaf upgrade-campaign {
      description
        "The upgrade campaign of the attempts, as the device reports it.";
      type string;
    }
    leaf target-release {
      description
        "The target release of the attempts.";
      type string;
    }
    list attempt {
      description
        "The device's attempts at target-release in upgrade-campaign.";
      key number;
      leaf number {
        type uint32;
      }
      uses attempt-status;
    }
    uses vetoes;
  }
}
