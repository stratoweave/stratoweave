module software {
  yang-version "1.1";
  namespace "urn:fleetmgr:software";
  prefix sw-cfs;

  import stratoweave {
    prefix sw;
  }
  import maintenance {
    prefix maint;
  }
  import fleetmgr {
    prefix fleetmgr;
  }
  import fleetmgr-types {
    prefix fleetmgr-types;
  }
  import stratoweave-images {
    prefix sw-img;
  }

  grouping plan-layout {
    list window {
      description
        "One planned window occurrence: which schedule it came from, when
         it opens and closes as absolute times, and the devices placed in
         it. An always-open window has no end.";
      key "schedule start";
      leaf schedule {
        description "Name of the window's source; a campaign without
           windows plans into one synthetic default window.";
        type string;
      }
      leaf start {
        description "Seconds since the Unix epoch.";
        type uint64;
        units "seconds";
      }
      leaf end {
        description "Seconds since the Unix epoch.";
        type uint64;
        units "seconds";
      }
      list device {
        key name;
        description
          "A device the controller has released stays in the window it
           was released in, with its real times.";
        leaf name {
          type string;
        }
        leaf estimated-start {
          description "Seconds since the Unix epoch; an estimate, for a
             device not released yet.";
          type uint64;
          units "seconds";
        }
        leaf estimated-duration {
          type uint32;
          units "seconds";
        }
        leaf prepare-start {
          description
            "Seconds since the Unix epoch: when the campaign let the device
             prepare its image in this run, or, for a device that waits to
             prepare, when it will. Absent when the device does not prepare
             before its window.";
          type uint64;
          units "seconds";
        }
        leaf started {
          description "Seconds since the Unix epoch, when the controller
             released the device.";
          type uint64;
          units "seconds";
        }
        leaf finished {
          description "Seconds since the Unix epoch, when the device
             reported that its upgrade ended.";
          type uint64;
          units "seconds";
        }
      }
    }
    leaf-list alarm {
      description
        "Placement problems, such as devices that did not fit, the
         devices that are held, and the members that cannot prepare
         before their window, or that wait for it after a failed
         prepare.";
      type string;
    }
  }

  container software {
    list upgrade-campaign {
      key name;

      sw:transform fleetmgr.cfs.UpgradeCampaign {
          sw:direct-output;
      }
      sw:link schedules {
        sw:path /maint:schedules;
      }
      sw:link redundancy-groups {
        sw:path /fleetmgr:redundancy-groups;
      }
      sw:link images {
        sw:path /sw-img:images;
      }
      leaf name {
        type string;
      }
      leaf allow-staging {
        description
          "Whether the members prepare their image before their window:
           copy it to the device, with no outage, while the campaign's veto
           holds the install. In run, the campaign lets each member that
           needs the upgrade, and that the plan gives a window, prepare
           once. The first prepares at once. The others follow, as far
           apart as their deadlines allow: the opening of the next window
           of the member's schedule that the campaign uses, less
           close-margin percent of its expected prepare time. No member
           prepares while such a window is open. In plan nothing is copied.
           A failed prepare is not tried again. The upgrade in the window
           copies the image again, so windows are not shorter.";
        type boolean;
        default "false";
      }
      list device {
        key name;
        description
          "Devices this campaign upgrades. A device in the fleet is in one
           campaign at most, also while the campaign is in plan or after it
           is done: an edit that names it in a second campaign fails. Delete
           the campaign, or remove the device from it, to free the device.
           A device that is not in the fleet gets nothing from a campaign,
           so two campaigns can name it; the edit that adds it to the fleet
           then fails until only one campaign names it. A device that is
           removed and added again is a new member, and its device keeps
           the final status of its attempt: a member that failed counts as
           failed until it has a new attempt.";
        leaf name {
          sw:link inventory;
          type leafref {
            path "/fleetmgr:fleet/fleetmgr:device/fleetmgr:name";
          }
        }
        leaf image {
          description
            "The image this device installs, from the image list. Its
             version is the release the device should run.";
          type leafref {
            path "/sw-img:images/sw-img:image/sw-img:name";
          }
          mandatory true;
        }
        leaf attempt {
          description
            "Change it to try the device again. The campaign then takes the
             device as a new member: it reads its release again and is held
             until it answers the new attempt, so a member that failed is
             upgraded again in a window. A member that succeeded answers
             up-to-date. A member in flight gets the campaign's veto back:
             its run stops before the install, or, past the install,
             finishes and holds its slot until it ends. When that run fails
             its rollback, the new attempt does not start: the member shows
             not-started, counts as failed, and holds its redundancy groups
             until it has another attempt. Any new value counts.";
          type uint32;
          default "0";
        }
      }
      leaf admin-state {
        description
          "plan: every member in the fleet gets the campaign's name, its
           attempt and the veto campaign:NAME, which holds its install, and the
           target release and image URL of its image when the image is in
           the image list and has a version. Each member reads the release
           it runs and answers up-to-date or upgrade-needed. Nothing is
           installed.
           A member in flight when the campaign goes from run to plan stops
           before its install; a member past its install finishes. The plan
           shows what a new run would do.
           run: the campaign releases each member that has answered in a
           window of its schedule by removing the veto, and puts the veto
           back when the member is done. A member that still upgrades from
           before the run, after a pause or a restart, counts in flight and
           keeps the veto.";
        type enumeration {
          enum plan;
          enum run;
        }
        default plan;
      }

      leaf default-schedule {
        description
          "Schedule for members whose device has no binding of its own.
           Devices bound to a schedule are placed only in its windows, and
           devices that do not fit are not actuated and surface as alarms
           in the plan. A campaign with no default and no bound members
           gets one synthetic window that opens at launch, or after
           notification-period, and never closes; a deadline closes it
           like any window.";
        type leafref {
          path "/maint:schedules/maint:schedule/maint:name";
        }
      }
      leaf deadline {
        description
          "When the campaign must be finished, as seconds since the Unix
           epoch. The deadline cuts off the window supply: only window
           time before it counts, and the concurrency it needs is computed
           backwards from it. Devices that cannot be placed before the
           deadline surface as alarms.";
        type uint64;
        units "seconds";
      }
      leaf notification-period {
        description
          "How long before a window the customers of its members must
           know about it. The campaign uses only the windows that open this
           long or more after run-since in state, or after now before the
           first run. It leaves out a window that opens earlier, also when
           the window closes later. A member added later, and a member that
           is up to date, gets no notice of its own: it gets the first
           window that the campaign can use. A larger value during a run
           takes windows away, and their waiting members get the next
           window that is left. 0 gives no notice.";
        type uint16;
        units "days";
        default 0;
      }
      container memory {
        sw:memory;
        description
          "What fleetmgr keeps for the campaign. A value configured here has
           no effect.";
        leaf run-since {
          description "The run-since of state.";
          type uint64;
          units "seconds";
        }
      }
      leaf target-concurrency {
        description
          "How many devices upgrade at the same time while the campaign
           is on schedule. The controller starts with one device and
           grows toward this number as devices finish without a failure.
           It goes above it only when a window or the deadline needs
           more, up to max-concurrency.";
        type uint32 {
          range "1..max";
        }
        units "devices";
        default 10;
      }
      leaf max-concurrency {
        description
          "The most devices that upgrade at the same time, also when a
           window or the deadline needs more. A deadline that needs more
           raises an alarm. A value below target-concurrency counts as
           target-concurrency.";
        type uint32 {
          range "1..max";
        }
        units "devices";
        default 50;
      }
      leaf close-margin {
        description
          "How much time a device must have left before its window
           closes to start there, in percent of its slow time. The slow
           time is the 98th percentile of the last upgrade times, two
           rounds at max-concurrency and at least 50, or the mean of the
           last round and a quarter at target-concurrency when that is
           longer, scaled to the device's estimate. 150 starts a device
           only while one and a half times its slow time is left. When
           the margin is longer than the time left in every window of a
           device's schedule, the device starts in no window, and the
           plan says so.";
        type uint16 {
          range "100..max";
        }
        units "percent";
        default 150;
      }
      leaf stagger {
        description
          "How long the campaign takes to start as many devices as its
           concurrency, in percent of the expected upgrade time. The
           starts are spread evenly, so when a window opens with room for
           many devices, they start one after the other, and a larger
           campaign starts them faster. At 100, the devices that fill a
           window start over one upgrade time, and then as fast as devices
           end on average; below 100 the starts can also catch up when more
           devices end at once. 0 starts them all at once.";
        type uint16 {
          range "0..100";
        }
        units "percent";
        default 25;
      }
      leaf failure-budget {
        description
          "The most members that may fail, in percent of the members the
           campaign has now, rounded down to whole devices: 0.5 percent of
           1000 members is 5 devices. A member has failed while its status
           for this campaign's intent is failed or rolled-back. When more
           members have failed than the budget, no more members start or
           prepare, and the plan gives an alarm. Without a budget, any
           number of members may fail.";
        type decimal64 {
          fraction-digits 2;
          range "0..100";
        }
        units "percent";
      }

      container state {
        config false;
        leaf run-since {
          description
            "When the campaign first went to run, as seconds since the Unix
             epoch. A pause and a restart of fleetmgr keep it, and deleting
             the campaign clears it. Absent before the first run.";
          type uint64;
          units "seconds";
        }
        leaf total {
          type uint32;
        }
        leaf in-progress {
          description
            "Counts only the statuses that are for this campaign's intent:
             the device reports them for its name and the member's target
             release.";
          type uint32;
        }
        leaf succeeded {
          description
            "Counts only the statuses that are for this campaign's intent:
             the device reports them for its name and the member's target
             release. Includes up-to-date.";
          type uint32;
        }
        leaf failed {
          description
            "Counts only the statuses that are for this campaign's intent:
             the device reports them for its name and the member's target
             release. Includes rolled-back and not-started.";
          type uint32;
        }
        leaf preparing {
          description
            "Members that wait for their release and prepare the target now:
             their status for this campaign's intent is upgrade-needed, and
             their prepare of the target runs.";
          type uint32;
        }
        leaf prepared {
          description
            "Members that wait for their release with the target prepared:
             their status for this campaign's intent is upgrade-needed, and
             their prepare of the target is done.";
          type uint32;
        }
        leaf held {
          description
            "Members that are held: the members that device-status gives
             a held reason.";
          type uint32;
        }
        container plan {
          description
            "The materialized plan: every window the campaign is placed
             into, the devices assigned to each, and their times: real for
             released devices, estimated for the rest. The companion actor
             computes it from the campaign; the transform actuates the same
             computation, so what runs is what is shown. Estimates, not
             guarantees. In plan, it is the plan of a run that starts now.
             Held members, such as the members that have not answered the
             campaign's target, upgrade-needed or a final status, get an
             alarm, and device-status says why. With allow-staging, each
             member's prepare-start says when it prepares.";
          uses plan-layout;
          leaf prepare-concurrency {
            description
              "The most members that prepare at once, each from its
               prepare-start for its expected prepare time, the prepares
               that run now included. Absent when no member prepares.";
            type uint32;
            units "devices";
          }
        }
        list device-status {
          key device;
          description
            "The attempt that counts for the member, as its device reports
             it: the attempt that is in-progress, when the device runs one
             at the campaign's target, and else the member's attempt. status
             is pending when the device has not answered that attempt. Of
             the statuses, only upgrade-needed and the final ones answer the
             campaign's target; a member that shows unknown or pending has
             not answered, and the plan holds it.";
          leaf device {
            type string;
          }
          leaf attempt {
            description
              "The attempt that status is for.";
            type uint32;
          }
          uses fleetmgr-types:attempt-status;
          uses fleetmgr-types:vetoes;
          leaf version {
            description "Release the device runs, from its platform.";
            type string;
          }
          leaf model {
            description "Chassis model of the device, from its platform.";
            type string;
          }
          leaf held {
            description
              "Why the member waits and may not start now: the first of
               these reasons that applies to it. Absent when it is not
               held. A held member keeps the window promised to it. When
               that window closes, its promise moves to the next window
               of its schedule, and the plan gives an alarm.";
            type enumeration {
              enum down {
                description "The flotilla is not connected to the device.";
              }
              enum flotilla-down {
                description
                  "The top is not connected to the device's flotilla.
                   held-by names the flotilla.";
              }
              enum not-answered {
                description "It has not answered the campaign's target.";
              }
              enum vetoed {
                description
                  "Its device has a veto of another holder than the
                   campaign, which holds the install. held-by names the
                   holder.";
              }
              enum group-failed {
                description
                  "It waits behind a member of its redundancy groups that
                   failed. held-by names that member.";
              }
              enum group-down {
                description
                  "It waits behind a member of its redundancy groups that
                   is down. held-by names that member.";
              }
              enum group-not-answered {
                description
                  "It waits behind a member of its redundancy groups that
                   has not answered. held-by names that member.";
              }
              enum group-vetoed {
                description
                  "It waits behind a member of its redundancy groups that
                   is vetoed. held-by names that member.";
              }
              enum failure-budget {
                description
                  "More members have failed than the failure budget.";
              }
            }
          }
          leaf held-by {
            description
              "The device or the flotilla that holds the member, when
               another one does, or the holder of the veto that holds it.
               When several hold it, one of them.";
            type string;
          }
        }
      }
    }
  }
}
