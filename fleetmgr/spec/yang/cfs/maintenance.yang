module maintenance {
  yang-version "1.1";
  namespace "urn:fleetmgr:maintenance";
  prefix maint;

  import stratoweave {
    prefix sw;
  }

  container schedules {
    description
      "The named maintenance schedules: generators of the absolute window
       occurrences in which impacting work on the devices bound to a
       schedule may run. Devices bind to a schedule by name on their
       inventory entry and campaigns name one as their default, so a
       schedule outlives any one campaign. The container is a transform
       so campaigns can link it and re-plan when any schedule changes.";

    sw:transform fleetmgr.cfs.Schedules;

    list schedule {
      key name;
      leaf name {
        type string;
      }
      leaf utc-offset {
        description
          "The schedule's local timezone, as minutes east of UTC. A stand
           in until proper timezone names arrive: it pretends there is no
           daylight saving.";
        type int16 {
          range "-720..840";
        }
        units "minutes";
        default 0;
      }
      list window {
        description
          "One recurrence rule: the window opens at the local time of day
           on the listed weekdays, and every day when none are listed.";
        key "at";
        leaf at {
          description
            "Local time of day the window opens, as seconds after
             midnight.";
          type uint32 {
            range "0..86399";
          }
          units "seconds";
        }
        leaf duration {
          type uint32;
          units "seconds";
          mandatory true;
        }
        leaf-list day {
          type enumeration {
            enum mon;
            enum tue;
            enum wed;
            enum thu;
            enum fri;
            enum sat;
            enum sun;
          }
        }
      }
    }
  }
}
