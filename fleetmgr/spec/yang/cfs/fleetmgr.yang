module fleetmgr {
  yang-version "1.1";
  namespace "urn:fleetmgr:fleetmgr";
  prefix fleetmgr;

  import stratoweave {
    prefix sw;
  }
  import maintenance {
    prefix maint;
  }
  import fleetmgr-types {
    prefix fleetmgr-types;
  }

  container fleet {
    list device {
      key name;

      sw:transform fleetmgr.cfs.Device;

      leaf name {
        type string;
      }

      leaf type {
        description "Device platform type understood by the owning flotilla.";
        type string;
        mandatory true;
      }

      leaf schedule {
        description
          "Maintenance schedule this device is bound to. A campaign places
           the device only in windows of this schedule; without a binding
           the campaign's default schedule applies.";
        type leafref {
          path "/maint:schedules/maint:schedule/maint:name";
        }
      }

      leaf-list redundancy-group {
        description
          "The redundancy groups this device is a member of. The members of
           a group back each other up, so a campaign upgrades them one at a
           time, in order of redundancy-priority, and as far apart as the
           group's entry under /redundancy-groups says. The group's
           failure-policy says whether the other members go on after a
           member fails.";
        type string;
      }

      leaf redundancy-priority {
        description
          "Where this device comes in each of its redundancy groups: lower
           first, and equal priorities in order of device name.";
        type uint16;
        default 100;
      }

      uses fleetmgr-types:device-options;
      uses fleetmgr-types:upgrade-checks;

      container state {
        config false;
        container platform {
          description
            "Absent until the device has connected.";
          uses fleetmgr-types:platform;
        }
      }
    }
  }

  container redundancy-groups {
    description
      "How far apart the members of a redundancy group upgrade, and what a
       failed member does to the others. A group that has no entry here
       spreads, with no min-separation, and continues after a failure. The
       container is a transform so campaigns can link it and re-plan when
       an entry changes.";

    sw:transform fleetmgr.cfs.RedundancyGroups;

    list redundancy-group {
      key name;

      leaf name {
        description "The group, as devices name it under redundancy-group.";
        type string;
      }

      leaf separation-policy {
        description
          "spread: when the plan first gives the members their windows, it
           moves later members to later windows of the campaign, up to as
           far apart as those windows allow. A member moves only by trading
           windows with a device of the same estimate in no group, and only
           when no device then misses its window. pack: each member starts
           as soon as the member before it is done.";
        type enumeration {
          enum spread;
          enum pack;
        }
        default spread;
      }

      leaf min-separation {
        description
          "The least time from when one member is done until the next may
           start, for either policy.";
        type uint32;
        units "seconds";
        default 0;
      }

      leaf failure-policy {
        description
          "continue: a member that failed or rolled back holds the other
           members only until it is done and up again; the next member
           then starts after min-separation. A member whose rollback
           failed is in an unknown state, and holds the other members until
           an operator acts, as under hold. So does a member whose attempt
           did not start after the rollback of an earlier one failed. hold: while a member is failed,
           the other members wait for an operator: a new attempt, a removal, or a
           success that the member reports later.";
        type enumeration {
          enum continue;
          enum hold;
        }
        default continue;
      }
    }
  }
}
