module fleetmgr-rfs {
  yang-version "1.1";
  namespace "urn:fleetmgr:rfs";
  prefix fleetmgr-rfs;

  import stratoweave {
    prefix sw;
  }
  import stratoweave-rfs {
    prefix sw-rfs;
  }
  import fleetmgr-types {
    prefix fleetmgr-types;
  }

  augment "/sw-rfs:rfs" {
    list device {
      key name;

      sw:rfs-transform fleetmgr.rfs.Device;

      leaf name {
        type string;
      }

      leaf type {
        type string;
        mandatory true;
      }

      uses fleetmgr-types:device-options;
      uses fleetmgr-types:upgrade-checks;
      uses fleetmgr-types:software-options;

      container state {
        config false;
        description
          "What the flotilla reports for this device: the software state
           from its /device/software/state, and the platform and the
           connection from its /device/state. One container, so one
           subscription takes them all: a subtree filter of two branches
           drops a device while either is absent.";
        uses fleetmgr-types:upgrade-status;
        container platform {
          uses fleetmgr-types:platform;
        }
        leaf connected {
          description
            "Whether the flotilla is connected to the device: its
             /device/state/adapter entry of the device's type. Absent
             until that entry first says connected, and while the
             flotilla has no such entry.";
          type boolean;
        }
      }
    }
  }
}
