module flotilla-rfs {
  yang-version "1.1";
  namespace "urn:fleetmgr:flotilla-rfs";
  prefix flotilla-rfs;

  import stratoweave {
    prefix sw;
  }
  import stratoweave-rfs {
    prefix sw-rfs;
  }

  typedef health {
    type enumeration {
      enum healthy;
      enum unhealthy;
    }
  }

  grouping verdict {
    leaf health {
      type health;
    }
    leaf detail {
      type string;
    }
  }

  augment "/sw-rfs:rfs" {
    container device-health {
      description
        "Health checks read off the device all the time. bgp: which sessions
         are established and how many prefixes the device advertises.
         interfaces: which interfaces are up with their line protocol up.
         ospf: the OSPF neighbors and their adjacency state. Every read is judged by the check's pre-check rule and post-check
         rule; state shows the verdicts and the reads they were based on.
         Each check is also one of the device's software upgrade pre-checks
         and post-checks, registered under its name. A pre-check records a
         baseline; the post-check passes once the device is back at that
         baseline, judged on a read taken after the reload. Emits no device
         configuration.";

      sw:rfs-transform flotilla.rfs.DeviceHealth;

      leaf enabled {
        type boolean;
        default "true";
      }

      leaf poll-period {
        description
          "Seconds between reads for a check while its upgrade check runs. A check answers from the first read taken after it
           started, so this bounds how long it waits.";
        units "seconds";
        type uint16 {
          range "1..max";
        }
        default 2;
      }

      leaf precheck-wait {
        description
          "Seconds a pre-check waits for a read that passes before it
           refuses. Keep it below the software manager's 60 s pre-check
           deadline, or the check counts as not answering.";
        units "seconds";
        type uint16 {
          range "1..max";
        }
        default 45;
      }

      leaf postcheck-wait {
        description
          "Seconds a post-check waits for the device to get back to the
           pre-check's baseline before it refuses, which aborts the
           activation. Keep it below the software manager's 900 s post-check
           deadline.";
        units "seconds";
        type uint16 {
          range "1..max";
        }
        default 600;
      }

      leaf health-period {
        description
          "Seconds between reads for a check while its upgrade check does
           not run.";
        units "seconds";
        type uint16 {
          range "1..max";
        }
        default 30;
      }

      container state {
        config false;
        description
          "The checks applied to the last reads of the device. Published
           when a verdict or a read changes.";
        leaf health {
          description
            "healthy when every check that has read the device passes.
             Absent until the first read.";
          type health;
        }
        leaf since {
          description
            "When health last changed, as yang:date-and-time.";
          type string;
        }
        list check {
          key name;
          leaf name {
            description "bgp, interfaces or ospf.";
            type string;
          }
          leaf health {
            description "healthy when both rules pass.";
            type health;
          }
          container precheck {
            description "Would an upgrade start now.";
            uses verdict;
          }
          container postcheck {
            description "Is the device back at the baseline.";
            uses verdict;
          }
          leaf baseline-at {
            description
              "When the baseline was taken, as yang:date-and-time: by an
               upgrade's pre-check, or by the first read the pre-check rule
               passes.";
            type string;
          }
        }
        container bgp {
          description
            "The bgp check. The pre-check rule fails while sessions are
             configured and none is established. The post-check rule wants
             as many sessions established and routes advertised as at the
             baseline.";
          container baseline {
            leaf established {
              type uint32;
            }
            leaf advertised {
              type uint64;
            }
          }
          list neighbor {
            description "The BGP neighbors of the last read.";
            key address;
            leaf address {
              type string;
            }
            leaf session-state {
              type string;
            }
            leaf advertised {
              description "Prefixes the device sends to this neighbor.";
              type uint64;
            }
            leaf received {
              description "Prefixes the device has from this neighbor.";
              type uint64;
            }
          }
        }
        container interfaces {
          description
            "The interfaces check. The pre-check rule passes on every read.
             The post-check rule fails when an interface that was up, line
             protocol up, at the baseline is not any more, NVI and
             Virtual-Access interfaces aside, or when fewer Virtual-Access
             interfaces are up than at the baseline.";
          list interface {
            description
              "The interfaces of the last read, and those up at the baseline
               that it lacks.";
            key name;
            leaf name {
              type string;
            }
            leaf admin-status {
              type string;
            }
            leaf oper-status {
              type string;
            }
            leaf up-at-baseline {
              description "Up, line protocol up, when the baseline was taken.";
              type boolean;
            }
          }
        }
        container ospf {
          description
            "The ospf check. The pre-check rule passes on every read. The
             post-check rule fails unless the neighbors are the baseline's,
             each in the same adjacency state: none missing, none new.";
          list neighbor {
            description
              "The OSPF neighbors of the last read, and those of the baseline
               that it lacks.";
            key "neighbor-id interface";
            leaf neighbor-id {
              description "The neighbor's router ID.";
              type string;
            }
            leaf interface {
              type string;
            }
            leaf address {
              type string;
            }
            leaf state {
              description "ospf-nbr-full once the adjacency is up.";
              type string;
            }
            leaf state-at-baseline {
              description "The state when the baseline was taken; absent if new.";
              type string;
            }
          }
        }
      }
    }
  }
}
