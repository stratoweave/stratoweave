module Cisco-IOS-XE-bgp-oper {
  yang-version "1.1";
  namespace "http://cisco.com/ns/yang/Cisco-IOS-XE-bgp-oper";
  prefix bgp-ios-xe-oper;

  description
    "Pruned to the BGP neighbor readout the device-health service uses:
     session state and the prefix counts per peer. Keys match the full module
     so neighbors stay distinct per address family and VRF. Enumerations are
     kept as strings, like the other pruned device models, so an unexpected
     value parses instead of failing.";

  container bgp-state-data {
    config false;
    container neighbors {
      list neighbor {
        key "afi-safi vrf-name neighbor-id";
        leaf afi-safi { type string; }
        leaf vrf-name { type string; }
        leaf neighbor-id { type string; }
        leaf session-state {
          description "fsm-established once the session is up.";
          type string;
        }
        container prefix-activity {
          container sent {
            leaf current-prefixes {
              description "Prefixes the device currently advertises to the peer.";
              type uint64;
            }
          }
          container received {
            leaf current-prefixes { type uint64; }
          }
        }
      }
    }
  }
}
