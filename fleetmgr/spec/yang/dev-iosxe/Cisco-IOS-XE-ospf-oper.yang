module Cisco-IOS-XE-ospf-oper {
  yang-version "1.1";
  namespace "http://cisco.com/ns/yang/Cisco-IOS-XE-ospf-oper";
  prefix ospf-ios-xe-oper;

  description
    "Pruned to what the device-health OSPF check uses: the neighbors per
     interface and their adjacency state, what `show ip ospf neighbor
     detail` lists. Keys match the full module. Enumerations and numbers
     are kept as strings, like the other pruned device models, so an
     unexpected value parses instead of failing.";

  container ospf-oper-data {
    config false;
    container ospf-state {
      presence "tbl-ospf";
      list ospf-instance {
        key "af router-id";
        leaf af { type string; }
        leaf router-id { type string; }
        list ospf-area {
          key "area-id";
          leaf area-id { type string; }
          list ospf-interface {
            key "name";
            leaf name { type string; }
            list ospf-neighbor {
              key "neighbor-id";
              leaf neighbor-id {
                description "The neighbor's router ID, dotted.";
                type string;
              }
              leaf address {
                description "The neighbor's interface address.";
                type string;
              }
              leaf state {
                description "ospf-nbr-full once the adjacency is up.";
                type string;
              }
            }
          }
        }
      }
    }
  }
}
