module Cisco-IOS-XE-interfaces-oper {
  yang-version "1.1";
  namespace "http://cisco.com/ns/yang/Cisco-IOS-XE-interfaces-oper";
  prefix interfaces-ios-xe-oper;

  description
    "Pruned to what the device-health interface check uses: each interface's
     admin and operational status, as `show interfaces` reports them. Up, line
     protocol up is admin-status if-state-up and oper-status
     if-oper-state-ready. Enumerations are kept as strings, like the other
     pruned device models, so an unexpected value parses instead of failing.";

  container interfaces {
    config false;
    list interface {
      key "name";
      leaf name { type string; }
      leaf admin-status {
        description "if-state-up unless the interface is shut down.";
        type string;
      }
      leaf oper-status {
        description "if-oper-state-ready while the line protocol is up.";
        type string;
      }
    }
  }
}
