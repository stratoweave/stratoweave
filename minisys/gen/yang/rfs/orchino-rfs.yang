module mini-rfs {
    yang-version "1.1";
    namespace "http://example.com/mini-rfs";
    prefix "mini-rfs";

    import stratoweave {
        prefix sw;
    }
    import stratoweave-rfs {
        prefix sw-rfs;
    }
    import ietf-inet-types {
      prefix inet;
    }

    augment "/sw-rfs:rfs" {
        list snmp-interface {
            key "if-index";
            sw:rfs-transform mini.rfs.SnmpInterface;
            description
              "Poll an IF-MIB interface using generated YANG paths.";

            leaf if-index {
                type int32 { range "1..2147483647"; }
            }
            leaf period-ms {
                type uint32 { range "10..3600000"; }
                default 1000;
            }
            container state {
                config false;
                leaf descr { type string; }
                leaf oper-status { type string; }
                leaf in-octets { type uint64; }
                leaf out-octets { type uint64; }
                leaf error { type string; }
            }
        }

        container base-config {
            presence "Configure the device's NETCONF system settings.";
            sw:rfs-transform mini.rfs.BaseConfig;

            leaf name {
                type string;
                mandatory true;
            }

            leaf ipv4-address {
                type string;
                mandatory true;
            }

            container dynstate {
                sw:dynstate;
                leaf current-datetime {
                    type string;
                }
            }

            container state {
                config false;
                leaf current-datetime {
                    type string;
                }
            }
        }

        list l3vpn-endpoint {
            key "interface-name";

            sw:rfs-transform mini.rfs.L3vpnEndpoint;

            leaf vpn-name {
                type string;
                mandatory true;
            }

            leaf customer-name {
                type string;
                mandatory true;
            }

            leaf route-distinguisher {
                type string;
                mandatory true;
            }

            leaf import-rt {
                type string;
                mandatory true;
            }

            leaf export-rt {
                type string;
                mandatory true;
            }

            leaf interface-name {
                type string;
                mandatory true;
            }

            leaf ipv4-address {
                type inet:ipv4-address-no-zone;
                mandatory true;
            }

            leaf prefix-length {
                type uint8 {
                    range "0..32";
                }
                mandatory true;
            }

            leaf mtu {
                type uint16;
                mandatory true;
            }

            leaf vlan-id {
                type uint16;
            }

            leaf enabled {
                type boolean;
                mandatory true;
            }

            leaf site-code {
                type string;
            }

            leaf description {
                type string;
            }
        }
    }
}
