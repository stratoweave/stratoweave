module netinfra {
  yang-version "1.1";
  namespace "http://example.com/netinfra";
  prefix "netinfra";
  description "Network Infrastructure";
  revision 2019-01-01 {
    description "test revision";
    reference "ref1";
  }
  import stratoweave {
    prefix sw;
  }

  container netinfra {
    description "Network infrastructure";
    container global-settings {
      sw:transform mini.cfs.GlobalSettings;
      leaf asn {
        type uint32;
      }
    }
    list router {
      key name;

      sw:transform mini.cfs.Router;
      sw:link global {
        sw:path /netinfra/global-settings;
      }

      leaf name {
        type string;
      }
      leaf id {
        type uint32;
        description "router id";
        mandatory true;
      }
      leaf type {
        type string;
        mandatory true;
      }
      leaf mock {
        type boolean;
        default false;
      }
      container dynstate {
        sw:dynstate;
        leaf current-datetime {
          type string;
        }
      }
    }

  }
}
